#usage "This ULP allows users to import Allegro placement \n"
       "files.                                                "
       "Jorge Garcia 07/09/2014                               "

/*
*******************************************************************************
* Jorge Garcia, Cadsoft Computer
* July 09, 2014
* 
* Copyright (c) 2014 Newark, Premier Farnell DBA Cadsoft Computer
* 
* Permission is hereby granted, free of charge, to any person obtaining a copy 
* of this software and associated documentation files (the "Software"), to deal 
* in the Software without restriction, including without limitation the rights 
* to use, copy, modify, merge, publish, distribute, sublicense, and/or sell 
* copies of the Software, and to permit persons to whom the Software is 
* furnished to do so, subject to the following conditions:
* 
* The above copyright notice and this permission notice shall be included in 
* all copies or substantial portions of the Software.
* 
* THE SOFTWARE IS PROVIDED "AS IS", WITHOUT WARRANTY OF ANY KIND, EXPRESS OR 
* IMPLIED, INCLUDING BUT NOT LIMITED TO THE WARRANTIES OF MERCHANTABILITY, 
* FITNESS FOR A PARTICULAR PURPOSE AND NONINFRINGEMENT. IN NO EVENT SHALL THE 
* AUTHORS OR COPYRIGHT HOLDERS BE LIABLE FOR ANY CLAIM, DAMAGES OR OTHER 
* LIABILITY, WHETHER IN AN ACTION OF CONTRACT, TORT OR OTHERWISE, ARISING 
* FROM, OUT OF OR IN CONNECTION WITH THE SOFTWARE OR THE USE OR OTHER DEALINGS 
* IN THE SOFTWARE.
*******************************************************************************
*/


/*
*******************************************************************************
*                               REVISION HISTORY                              
*                                                                             
*  -07/09/2014      Initial release
* 
*  -07/10/2014      Corrected the syntax for the move command.                                           
*                                                                             
*******************************************************************************
*/ 


/*
*******************************************************************************
*                       GLOBAL VARIABLES AND DEFINITIONS                      *
*******************************************************************************
*/

/* #include "/home/cadsoft/eagle/debug.ulp" */
string input;                                                                   /* Path to input file                                       */

/*
*******************************************************************************
*                               NON-GUI FUNCTIONS                             *
*******************************************************************************
*/

/*
*******************************************************************************
*                             ProcessFile()
* Description:      This function takes the placement file and creates a string
*                   array, consisting of commands to move components. Upon exit
*                   those commands are run within EAGLE.
* 
* Argument(s):      file    Location of the placement file to be processed
* 
* Return(s):        none
* 
* Caller(s):        main()
* 
*******************************************************************************
*/  

void ProcessFile(string file) {
    string command;                                                             /* Stores big command string for EAGLE                      */
    string lines[];                                                             /* This array will hold the lines of the text file          */
    string parameters[];                                                        /* Intermediate array stores the parsed lines               */
    string out[];                                                               /* Stores all of the commands which which will then be ...  */
                                                                                /* joined as one big string, then passed to EAGLE.          */
    int nlines;                                                                 /* Number of lines in file                                  */
    int i;
    int m=0;
    int elem;
    int pos;     

    nlines = fileread(lines, file);
    
    for(i = 0; i < nlines; i++) {
        elem = strsplit(parameters, lines[i], ' ');
        /*sprintf(debug,"%d", elem);
        done = Debug(debug); 
        done = Debug(parameters[0]+"\n"+parameters[1]+"\n"+parameters[2]+"\n"+parameters[3]+"\n"+parameters[4]+"\n"+parameters[5]+"\n"+parameters[6]+"\n"); */
        if (i == 0) {                                                           /* First line of file, specifies units                      */
            if (strstr(strlwr(parameters[2]), "mil") >= 0) {
                out[m] = "GRID mil;";
                m++;
            }
            else if (strstr(strlwr(parameters[2]), "in") >= 0) {
                out[m] = "GRID in;";
                m++;
            }
            else if (strstr(strlwr(parameters[2]), "mm") >= 0) {
                out[m] = "GRID mm;";
                m++;
            }
        }
        else {
            out[m] = "MOVE '"+parameters[1]+"' ("+parameters[2]+" "+parameters[3]+");";
            /* done = Debug(out[m]); */
            m++;
            out[m] = "ROTATE =R"+parameters[4]+" '"+parameters[1]+"';";
            /* done = Debug(out[m]); */
            m++;
            if (parameters[5] == "m") {
                out[m] = "MIRROR '"+parameters[1]+"';";
                /* done = Debug(out[m]); */
                m++;
            }
        }
    }
    
    out[m] = "GRID LAST;";
    command = strjoin(out, ' ');
    
    exit(command);
}

/*
*******************************************************************************
*                                   MAIN()                                    *
*******************************************************************************
*/

int main() {
    int Result = dlgDialog("Import Allegro placement file") {
        dlgLabel("Please select a file to import by clicking browse.");
        dlgHBoxLayout {
            dlgStringEdit(input);
            dlgPushButton("Bro&wse") {
                input = dlgFileOpen("Select a file");
            }
        }
        dlgHBoxLayout {
            dlgPushButton("Process") ProcessFile(input);
            dlgPushButton("Cancel") dlgReject();
        }
    };
    return Result;
}
